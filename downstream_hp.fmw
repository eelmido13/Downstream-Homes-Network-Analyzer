FME workspace downstream_hp.fmw

Parameters:
- OLTName = OLT161   # Enter Text Data
- email_address = eelmido@entegro.ie
- SourceDataset_POSTGRES_4 = VMK Public DB (postgres User)   # Connection
- SourceDataset_POSTGIS_5 = VMK Public DB (postgres User)   # Connection
- SourceDataset_POSTGIS_7 = VMK Public DB (postgres User)   # Connection
- SourceDataset_POSTGIS = VMK Public DB (postgres User)   # Connection

Readers:
- POSTGRES_2: POSTGRES from $(SourceDataset_POSTGRES_4)
- POSTGIS_2: POSTGIS from $(SourceDataset_POSTGIS_5)
- POSTGIS_1: POSTGIS from $(SourceDataset_POSTGIS)
- POSTGIS_3: POSTGIS from $(SourceDataset_POSTGIS_7)
- ARCGISONLINEFEATURES_1: ARCGISONLINEFEATURES
- ARCGISONLINEFEATURES_2: ARCGISONLINEFEATURES
- ARCGISONLINEFEATURES_3: ARCGISONLINEFEATURES

boundaries (reader POSTGIS_2)
    attributes: objectid int4, level_ int4,BTree, name varchar(50), homes int4, loc_desc varchar(4), comments varchar(254), kta_code varchar(254), bw_ref_id varchar(80), globalid varchar(38), creationdate timestamp, creator varchar(128), editdate timestamp, editor varchar(128), shape__area float8, shape__length float8, import_date varchar(200), modified_date varchar(200), olt_area varchar(200), build_status int4, id serial,PrimaryKey, ent_id uuid,Unique, ent_editdate timestamp, ent_creatdate timestamp, ent_editor varchar(30), ent_creator varchar(30), design_type int4, ent_status int4, build_rating int4, import_client_ip_address varchar(200), import_pg_user varchar(200),
      modified_client_ip_address varchar(200), modified_pg_user varchar(200), cable_origin varchar(50), cei_reference varchar(50), sdsi_reference varchar(50), total_duct_length float8, subduct_size int4
    -> Tester_3
Tester_3
    BOOL_OP = OR
    TEST_CLAUSE = TEST @Value(ent_status) != 1
    TEST_MODE = TEST
    PASSED -> FeatureReader [INITIATOR]
FeatureReader
    ATTRIBUTES = public.boundaries,"objectid,level_,name,homes,loc_desc,comments,kta_code,bw_ref_id,globalid,creationdate,creator,editdate,editor,shape__area,shape__length,import_date,modified_date,olt_area,build_status,id,ent_id,ent_editdate,ent_creatdate,ent_editor,ent_creator,design_type,ent_status,build_rating,import_client_ip_address,import_pg_user,modified_client_ip_address,modified_pg_user,cable_origin,cei_reference,sdsi_reference,total_duct_length,subduct_size",public.chambers,"objectid,status,angle,comments,label,spec_id,constructi,ownership,chmbexist,location,lidconditi,accessible,condition,popspace,pocspace,owner,depth,thirdparty,surface,chamber_lo,ch_type,ch_id,labx,laby,ent_id,ent_editdate,ent_creatdate,ent_creator,ent_editor,ch_condition,globalid,creationdate,creator,editdate,editor,import_date,modified_date,olt_area,id,ent_status,fid_1,import_client_ip_address,import_pg_user,modified_client_ip_address,modified_pg_user,civil_id,remedial_civils,civil_status,job_pack_id,mrl_license_no,civils_status,hazards,ipid,creator_1,assetid",public.feeder_cable,"objectid,label,status,owner,cab_size,cab_type,placement,prem_id,poc_id,length,ent_id,ent_editdate,ent_creatdate,ent_creator,ent_editor,duct_proving_status,cabling_status,ent_cable_qc,shape__length,globalid,creationdate,creator,editdate,editor,import_date,modified_date,olt_area,id,ent_status,fid_1,creationdate_1,creator_1,editdate_1,editor_1,sub_duct_type,pull_number,subduct_status,import_client_ip_address,import_pg_user,modified_client_ip_address,modified_pg_user,from_device,uplift,length_cabling_works,length_ducting_works,length_sub_ducting_work,length_blockages,length_proposed_duct,length_proposed_ducting_works,afp,pro_forma,design_status,bcr_no,to_device",public.fibre_cable,"objectid,label,status,owner,cab_size,cab_type,placement,prem_id,poc_id,length,ent_id,ent_editdate,ent_creatdate,ent_creator,ent_editor,globalid,creationdate,creator,editdate,editor,shape__length,import_date,modified_date,olt_area,id,ent_status,fid_1,route_status,date_built,built_by,date_spliced,spliced_by,splice_status,from_device,to_device,import_client_ip_address,import_pg_user,modified_client_ip_address,modified_pg_user",public.fibre_duct,"objectid,status,owner,location,surface,rc_type,duct_provi,length,comments,name,constructi,ownership,shape__len,ductuse,ductsize,distductsi,ductroped,stripdown,surface_ma,ent_id,ent_editdate,ent_creatdate,ent_creator,ent_editor,globalid,creationdate,creator,editdate,editor,shape__length,import_date,modified_date,olt_area,build_comments,duct_proving_status,width,depth,id,ent_status,ductfull,fid_1,creationdate_1,creator_1,editdate_1,editor_1,import_client_ip_address,import_pg_user,modified_client_ip_address,modified_pg_user,surface_verge,surface_fw,surface_cw,surface_carr_rc,civil_id,job_pack_id,mrl_license_no,civils_status,olt,a_length_surveyed,A_length_surveyed,olt_name,completed_date,completed_by,cei_no,cable_id",public.premises,"objectid,comments,location_i,geo_id,sw_id,sub_unit_g,sub_unit_s,contact_na,building_n,building_1,road,locality,town,county,prc,rtm_offici,self_insta,ed3_bb,hd,vod,dvr,voip_sip,channel_li,type,valid_,rtm_date,mmds_maint,mmds_ma_de,sub_cable,scma_descr,cpr_node,cpr_node_d,cpr_node_b,limited_bb,master_nod,master_n_1,report_nod,report_n_1,report_n_2,planning_m,planning_1,planning_c,voip_area,cell_id,easting,northing,latitude,longitude,horizon,loc_area_n,loc_area_r,voip_trigg,f360_mb_bb,network_bu,eircode,sw_date_ti,sub_unit_c,analogue_s,ig_easting,ig_northin,surveyyn,premstatus,hp_type,mdu_type,ent_id,ent_editdate,ent_creatdate,ent_creator,ent_editor,design_status,globalid,creationdate,creator,editdate,editor,import_date,modified_date,olt_area,pg_id,id,cabled_by,tested_by,tapped_by,cabled_date,tested_date,tapped_date,build_status,build_comments,pop_label,poc_label,ent_status,fid_1,drop_conn,release_st,status_date,nsa_reason,build_type_v,storeys,specialist_install,blocked,light_cabled_by,light_cabled_date,max_light,import_client_ip_address,import_pg_user,modified_client_ip_address,modified_pg_user,not_shrouded_shrouded_defective_date,not_shrouded_shrouded_defective_user,stopper,kmdu_ref,two_attachments",public.splice_closures,"objectid,label,owner,enc_type,enc_size,placement,prev_dev,reel_end,home_count,cable_leng,style_code,globalid,enclosure_,splice_cou,cabled_status,spliced_status,tested_status,cable_qc,splice_qc,enc_qc_mount,enc_qc_lab,cable_mgmt,chamber_tidy,enc_visual,overall_qc,comments,creationdate,creator,editdate,editor,import_date,link_loss_db,pon_id1,pon_id2,id,ent_id,ent_editdate,ent_creatdate,ent_editor,ent_creator,ent_status,status,tested_light_level,final_test_status,modified_date,import_client_ip_address,import_pg_user,modified_client_ip_address,modified_pg_user,olt_name,fas_version,floor"
    ATTR_ACCUM_MODE = Only Use Result
    CLIP_TO_ENVELOPE = NO
    COMBINE_GEOM = Use Result
    DATASET = VMK Public DB (postgres User)
    FEATURETYPES = public.boundaries public.chambers public.feeder_cable public.fibre_duct public.splice_closures public.fibre_cable public.premises
    FORMAT = POSTGIS
    GEOMETRY_TYPES = public.boundaries,"""geom,fme_area""",public.chambers,"""geom,fme_point""",public.feeder_cable,"""geom,fme_line""",public.fibre_cable,"""geom,fme_line""",public.fibre_duct,"""geom,fme_line""",public.premises,"""geom,fme_point""",public.splice_closures,"""geom,fme_point"""
    INITIATOR_FIRST_OUTPUT = default
    INTERACT = INTERSECTS
    ORDER_RESULTS = No
    OUTPUT_ADD_SCHEMA_ATTRIBUTES = NO
    OUTPUT_FEATURES_DISPLAY = Schema and Data Features
    POSTGIS_CREATE_FEATURE_TABLES_FROM_DATA = Yes
    POSTGIS_DISABLE_COLLECTION_SPLITTING = yes
    POSTGIS_FEATURES_PER_FETCH = 10000
    POSTGIS_NAMED_CONNECTION = VMK Public DB (postgres User)
    POSTGIS_QUERY_FEATURE_TYPES_FOR_MERGE_FILTERS = Yes
    POSTGIS_READ_TIME_WITH_TIMEZONE = Yes
    POSTGIS_USE_SEARCH_ENVELOPE = NO
    POSTGIS_USE_TRUE_POSTGIS_TYPES = yes
    public.chambers -> Junction_4
    public.fibre_cable -> Junction_19
    public.premises -> Junction_21
Note: Chambers
Junction_4
    -> Tester_6
Tester_6
    BOOL_OP = AND
    TEST_CLAUSE:
      TEST @Value(ent_status) != 1
      TEST @Value(status) != 2
      TEST @Value(owner) = 4
    TEST_MODE = TEST
    PASSED -> AttributeKeeper_5
boundaries (reader ARCGISONLINEFEATURES_1)
    attributes: OBJECTID OID, level_ Integer, name String(50), homes Integer, loc_desc String(4), comments String(254), kta_code String(254), bw_ref_id String(80), GlobalID GlobalID(38), CreationDate Date, Creator String(128), EditDate Date, Editor String(128), ent_id String(38), ent_editdate Date, ent_creatdate Date, ent_editor String(30), ent_creator String(30), design_type Integer, Shape__Area Double, Shape__Length Double, ent_status Integer, build_rating Integer, cable_origin String(50), cei_reference String(50), sdsi_reference String(50), total_duct_length Double, subduct_size Integer
    -> Junction_5
Note: PIA Boundaries
Junction_5
    -> AttributeKeeper_4
Note: Chambers
Junction
    -> NeighborFinder_3 [BASE]
splice_closures (reader ARCGISONLINEFEATURES_3)
    attributes: OBJECTID OID, label String(20), owner Integer, enc_type Integer, enc_size Integer, placement Integer, prev_dev String(20), reel_end Integer, home_count Integer, cable_leng Integer, style_code Integer, enclosure_ Double, splice_cou Double, cabled_status Integer, spliced_status Integer, Tested_status Integer, cable_qc Integer, splice_qc Integer, enc_qc_mount Integer, enc_qc_lab Integer, cable_mgmt Integer, chamber_tidy Integer, enc_visual Integer, overall_qc Integer, comments String(256), link_loss_db Double, ent_id String(38), ent_editdate Date, ent_creatdate Date, ent_editor String(30),
      ent_creator String(30), GlobalID GlobalID(38), CreationDate Date, Creator String(128), EditDate Date, Editor String(128), pon_id1 String(5000), pon_id2 String(5000), ent_status Integer, status Integer, tested_light_level String(20), final_test_status String(20), fas_version String(256), floor Integer
    -> Junction_2
Note: Splice Closure
Junction_2
    -> Tester_4
feeder_segments (reader ARCGISONLINEFEATURES_2)
    attributes: OBJECTID OID, fid_1 Double, label String(41), status Integer, owner Integer, cab_size Integer, cab_type Integer, placement Integer, prem_id Integer, poc_id Integer, length Double, ent_id String(256), ent_editdate Date, ent_creatdate Date, ent_creator String(30), ent_editor String(30), duct_proving_status Integer, cabling_status Integer, ent_cable_qc Integer, GlobalID GlobalID(38), CreationDate Date, Creator String(128), EditDate Date, Editor String(128), ent_status Integer, sub_duct_type Integer, pull_number String(20), subduct_status Integer, from_device String(99), Shape__Length Double,
      uplift Integer, length_cabling_works Double, length_ducting_works Double, length_sub_ducting_work Double, length_blockages Double, length_proposed_ducting_works Double, afp String(30), pro_forma String(30), design_status Integer, bcr_no String(30), to_device String(99)
    -> Junction_3
Note: Feeder Cable
Junction_3
    -> AttributeKeeper_6
Note: Distribution Network
Junction_25
    -> NeighborFinder [CANDIDATE]
Note: Distribution Chambers
Junction_24
    -> NeighborFinder [BASE]
Note: Ingress Chamber
Junction_14
    -> PointOnLineOverlayer [POINT]
Note: Splice_Closure
Junction_16
    -> Tester_5
Note: Feeder_Cable_Home_Count
Junction_11
    -> CoordinateExtractor_2
Note: Extract End point of line
CoordinateExtractor_2
    IND = -1
    RECURSIVE = No
    X_ATTR = _x
    Y_ATTR = _y
    Z_ATTR = _z
    MODE = Specify Coordinate
    -> VertexCreator_2
ShortestPathFinder
    ALLOW_UTURNS = No
    REORDER_CHOICE = None
    SNAP_POINTS = Yes
    SNAP_TOLERANCE = 1
    WEIGHT_ATTR_CHOICE = By Length
    PATH -> LineOnLineOverlayer [LINE]
LineOnLineOverlayer
    ATTRS_ACCUM_MODE_LOOKUP = ONE
    CLEANING_TOLERANCE_LOOKUP = NONE
    DEAGGREGATE_INPUT = Yes
    GENERATE_LIST_DROP = YES
    LIST_ATTRS_TO_INCLUDE = home_count
    LIST_NAME = list
    LOG_INTERSECTIONS = YES
    OV_ATTR = _overlaps
    SEPARATE_COLLINEAR_SEGMENTS = No
    ATTRS_ACCUM_MODE = Use Attributes From One Feature
    CLEANING_TOLERANCE = None
    LOG_LEVEL = Full
    LINE -> ListSummer
ListSummer
    RESULT = downstream_hp
    SRC_LIST = list{}.home_count
    -> NetworkFlowOrientor [LINE]
NetworkFlowOrientor
    DIRECTION_ATTR = _direction
    THREE_D = No
    NETWORK -> Orientor
    UNUSED -> Orientor
Orientor
    FLIP_APPEARANCES_LOOKUP = FLIP_APPEARANCES
    KIND = REVERSE
    FLIP_APPEARANCES_CHOICE = Yes
    ORIENTED -> PointOnLineOverlayer [LINE]
PointOnLineOverlayer
    ATTR_ACCUM_MODE = Merge Incoming
    ATTR_CONFLICT_RES_LOOKUP = ORIGINAL_IF_CONFLICT
    DEAGGREGATE_INPUT = Yes
    MEASURE_TYPE_LOOKUP = CONTINUOUS
    MERGE_MEASURES = Yes
    OV_ATTR = _overlaps
    TOLERANCE = 1
    ATTR_CONFLICT_RES = Use Original
    MEASURE_TYPE = Continuous
    POINT -> Tester_2
Tester_2
    BOOL_OP = OR
    TEST_CLAUSE:
      TEST downstream_hp ATTRIBUTE_VALUE_NULL ""
      TEST downstream_hp ATTRIBUTE_IS_MISSING ""
    TEST_MODE = TEST
    PASSED -> PointOnLineOverlayer_2 [POINT]
    FAILED -> AttributeKeeper_11
PointOnLineOverlayer_2
    ATTR_ACCUM_MODE = Merge Incoming
    ATTR_CONFLICT_RES_LOOKUP = ORIGINAL_IF_CONFLICT
    DEAGGREGATE_INPUT = Yes
    MEASURE_TYPE_LOOKUP = CONTINUOUS
    MERGE_MEASURES = Yes
    OV_ATTR = _overlaps
    TOLERANCE = 1
    ATTR_CONFLICT_RES = Use Original
    MEASURE_TYPE = Continuous
    POINT -> AttributeKeeper_11
AttributeKeeper_11
    CREATE_BULK_MODE_FEATURES = NO
    KEEP_ATTRS = name,downstream_hp
    -> Junction_12
Note: Merge Data to the PIA Boundaries
Junction_12
    -> Junction_13
CenterPointExtractor_2
    CENTX = _inside_x
    CENTY = _inside_y
    CENTZ = _inside_z
    EXTRACTIONMODE = CENTER
    -> FeatureMerger_2 [REQUESTOR]
pia_boundaries (reader POSTGIS_1)
    attributes: downstream_hp varchar(100), pia_ent_id varchar(200), level_ int4, name varchar(50), ent_status int4, cei_reference varchar(50), sdsi_reference varchar(50), total_duct_length float8, subduct_size int4, olt_name varchar(10), map_url varchar(250)
    -> ChangeDetector [ORIGINAL]
    -> DuplicateFilter_3
DuplicateFilter_3
    INPUT_ORDERED_CHOICE_LOOKUP = NO
    KEYATTR = name
    INPUT_ORDERED_CHOICE = No
Note: map_id
Junction_15
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(olt_name) @Value(olt_name) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> AttributeCreator_2
AttributeCreator_2
    ATTR_TABLE = SET_TO map_url (varchar(200)) = https://ipone.maps.arcgis.com/apps/mapviewer/index.html?webmap=@Value(map_id)&center=@Value(_inside_x),@Value(_inside_y),29903&level=20
    -> ChangeDetector [REVISED]

Bookmark: Downstream_Distribution
Junction_19
    -> AttributeKeeper
AttributeKeeper
    CREATE_BULK_MODE_FEATURES = NO
    KEEP_ATTRS = cab_size,cab_type,from_device,label,length,poc_id,prem_id,status,to_device,ent_status
    -> ent_status_2
ent_status_2: Tester
    BOOL_OP = OR
    TEST_CLAUSE = TEST @Value(ent_status) != 1
    TEST_MODE = TEST
    PASSED -> Snapper_2
Snapper_2
    EXTEND_LINES = NEVER
    SAVE_SHORT_LINES = No
    SNAPTYPE = END_NODE
    TOLERANCE = 1
    SNAPPED -> TopologyBuilder
    UNTOUCHED -> TopologyBuilder
TopologyBuilder
    ALLOW_CYCLES = No
    CLEANING_TOLERANCE_LOOKUP = AUTO
    DEAGGREGATE_INPUT = Yes
    GENERATION_MODE = INTERSECT
    MAX = 0
    OVERLAPPING_MODE = No
    START_EDGES = No
    BOUNDING_EDGES = All
    CLEANING_TOLERANCE = Automatic
    LINE -> CRCCalculator
CRCCalculator
    ALG_TYPE = CRC_32
    CRC_ATTR = _crc
    CRC_TYPE = GEOM_ENCODED
    ALG_CHOICES = CRC-32
    -> DuplicateFilter_5
DuplicateFilter_5
    INPUT_ORDERED_CHOICE_LOOKUP = NO
    KEYATTR = _crc
    INPUT_ORDERED_CHOICE = No
    UNIQUE -> Junction_18
Note: Premises
Junction_21
    -> AttributeKeeper_2
AttributeKeeper_2
    CREATE_BULK_MODE_FEATURES = NO
    KEEP_ATTRS = location_i,eircode
    -> CoordinateExtractor_5
CoordinateExtractor_5
    IND = 0
    RECURSIVE = No
    X_ATTR = _x
    Y_ATTR = _y
    Z_ATTR = _z
    MODE = Specify Coordinate
    -> FeatureMerger_7 [REQUESTOR]
Note: OLT
Junction_17
    -> NetworkCostCalculator [SOURCE]
Note: Feeder & FiberCable
Junction_18
    -> Snapper_3
Snapper_3
    EXTEND_LINES = NEVER
    SAVE_SHORT_LINES = No
    SNAPTYPE = END_NODE
    TOLERANCE = 1
    SNAPPED -> Junction_20
    UNTOUCHED -> Junction_20
Junction_20
    -> NetworkCostCalculator [LINE]
NetworkCostCalculator
    OUTPUT_CHOICE = MEASURE_VALUES
    SNAP_POINTS = Yes
    SNAP_TOLERANCE = 1.5
    WEIGHT_ATTR_CHOICE = By Length
    CONNECTED -> ShortestPathFinder_2 [NETWORK]
    CONNECTED -> Chopper_2
Chopper_2
    DEAGGREGATE_INPUT = Deaggregate
    MAX_VERTICES = 1
    MODE_LOOKUP = VERTEX
    REMNANT_ATTR = _remnant
    MODE = By Vertex
    CHOPPED -> MeasureExtractor_2
MeasureExtractor_2
    GET_MODE = POINT
    MEASURE_ATTR = _point_measure
    GEOM_TYPE = Point
    -> Matcher_2
Matcher_2
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _point_measure
    MATCH_STRATEGY_LOOKUP = MATCH
    MATCH_STRATEGY = Match Selected Attributes
    SINGLE_MATCHED -> Sorter_4
    NOT_MATCHED -> Sorter_4
Sorter_4
    SORT_PARM = _point_measure NUMERIC ASCENDING NON_VALUES_BEFORE_VALUES
    SORTED -> Counter_2
Counter_2
    CNT_ATTR = _count
    DOMAIN = counter
    SCOPE = Global
    START = 1
    -> AttributeKeeper_7
AttributeKeeper_7
    CREATE_BULK_MODE_FEATURES = NO
    KEEP_ATTRS = _count
    -> Junction_25
FeatureMerger_7
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> VertexCreator
VertexCreator
    ALLOW_DUPLICATES = NO
    CLOSE_LINES = Yes
    MEASURE_TYPE_LOOKUP = CONTINUOUS
    MISSING_VAL_MODE_LOOKUP = COMPUTE_NANS
    MODE = ADD
    REMOVE_ATTRIBUTES = No
    XVAL = @Value(x_s)
    YVAL = @Value(y_s)
    IGNORE_DUPLICATES = Yes
    MEASURE_TYPE = Continuous
    MISSING_VAL_MODE = Compute
    MODE_NAME = Add Point
    -> ShortestPathFinder_2 [FROM-TO]
ShortestPathFinder_2
    ALLOW_UTURNS = Yes
    REORDER_MODE = NONE
    SNAP_POINTS = Yes
    SNAP_TOLERANCE = 1
    THREE_D = No
    WEIGHT_ATTR_CHOICE = BY_LENGTH
    PATH -> LineOnLineOverlayer_2 [LINE]
LineOnLineOverlayer_2
    ATTRS_ACCUM_MODE_LOOKUP = ONE
    CLEANING_TOLERANCE_LOOKUP = AUTO
    DEAGGREGATE_INPUT = Yes
    GENERATE_LIST_DROP = YES
    LIST_ATTRS_TO_INCLUDE = _count
    LIST_NAME = _list
    OV_ATTR = _overlaps
    SEPARATE_COLLINEAR_SEGMENTS = No
    ATTRS_ACCUM_MODE = Use Attributes From One Feature
    CLEANING_TOLERANCE = Automatic
    LINE -> ListSummer_2
ListSummer_2
    RESULT = _sum
    SRC_LIST = _list{}._count
    -> AttributeKeeper_12
AttributeKeeper_12
    CREATE_BULK_MODE_FEATURES = NO
    KEEP_ATTRS = _sum
    -> AttributeRenamer
AttributeRenamer
    ATTR_TABLE = RENAME_SET_DEFAULT _sum > downstream_hp
    KEEP_RENAMED_ONLY = no
    MISSING_INPUT_ATTRS = REMOVE
    -> PointOnLineOverlayer_2 [LINE]

Bookmark: Chambers within PIA and intersects the Network
AttributeKeeper_5
    CREATE_BULK_MODE_FEATURES = NO
    KEEP_ATTRS = label,constructi,ent_id,accessible,angle,ch_condition,ch_id,ch_type,chamber_lo,chmbexist,civil_id,civil_status,civils_status,comments,condition,creationdate,depth,ent_status,hazards,id,import_client_ip_address,import_date,import_pg_user,ipid,job_pack_id,labx,laby,lidconditi,location,modified_client_ip_address,modified_date,modified_pg_user,mrl_license_no,objectid,olt_area,owner,ownership,pocspace,popspace,remedial_civils,spec_id,status,surface,thirdparty
    -> Junction_23
    -> Bufferer
Bufferer
    ANGLE = 22.5
    CAP_STYLE_LOOKUP = CAP_ARC
    CORNER_STYLE_LOOKUP = JOIN_ARC
    MODE = AREA
    OFFSET = .05
    OFFSET_UNITS = NONE
    PRECISION = APPROX
    CAP_STYLE = Arc
    CORNER_STYLE = Arc
    BUFFERED -> Chambers_PIA [CANDIDATE]
Chambers_PIA: Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> CoordinateExtractor
CoordinateExtractor
    LIST_NAME = _indices
    RECURSIVE = Yes
    MODE = All Coordinates
    -> ListExploder_2
ListExploder_2
    ATTR_CONFLICT_RES_LOOKUP = INCOMING_IF_CONFLICT
    INDEX_ATTR = _element_index
    LIST_ATTR = _indices{}
    ATTR_ACCUM_MODE = Merge List Attributes
    ATTR_CONFLICT_RES = Use List Attribute Values
    ELEMENTS -> AttributeCreator_5
AttributeCreator_5
    ATTR_TABLE:
      SET_TO itm_x (varchar(200)) = @Value(x)
      SET_TO itm_y (varchar(200)) = @Value(y)
    -> FeatureMerger_5 [REQUESTOR]
FeatureMerger_5
    JOIN_KEYS = @Value(ent_id) @Value(ent_id) AUTO
    MERGE_TYPE_VAL = GEOM_BUILD
    PROCESS_DUPS = NO
    REJECT_NULL_MISSING_KEYS = No
    SUPPLIERS_FIRST = No
    MERGE_TYPE = Geometry
    MERGED -> Junction

Bookmark: Identify Ingress and Egress
Junction_23
    -> FeatureMerger_5 [SUPPLIER]
AttributeCreator_6
    ATTR_TABLE:
      SET_TO downstream_hp (varchar(200))
      SET_TO olt_name (varchar(200)) = $(OLTName)
    -> Sorter_3
Sorter_3
    SORT_PARM = pia_ent_id NATURAL DESCENDING
    SORTED -> DuplicateFilter_2
DuplicateFilter_2
    INPUT_ORDERED_CHOICE_LOOKUP = NO
    KEYATTR = name
    INPUT_ORDERED_CHOICE = No
    UNIQUE -> AttributeManager_2
AttributeManager_2
    ATTR_TABLE = SET_TO subduct_size (int32) = FME_CONDITIONAL:DEFAULT_VALUE'_FME_NO_OP_'BOOL_OP;OR;COMPOSITE_TEST;1;TEST @Value(subduct_size) = 1'None'BOOL_OP;OR;COMPOSITE_TEST;1;TEST @Value(subduct_size) = 2'SDSI'BOOL_OP;OR;COMPOSITE_TEST;1;TEST @Value(subduct_size) = 3'VM - 18/14 Single'BOOL_OP;OR;COMPOSITE_TEST;1;TEST @Value(subduct_size) = 4'PIA'BOOL_OP;OR;COMPOSITE_TEST;1;TEST @Value(subduct_size) = 5'VM - 18/14 Twin'BOOL_OP;OR;COMPOSITE_TEST;1;TEST @Value(subduct_size) = 6'VM- 14/10 Single'BOOL_OP;OR;COMPOSITE_TEST;1;TEST @Value(subduct_size) = 7'VM - 32mm'BOOL_OP;OR;COMPOSITE_TEST;1;TEST @Value(subduct_size) = 8'VM - 28mm'BOOL_OP;OR;COMPOSITE_TEST;1;TEST @Value(subduct_size) = 9'VM - Micro - 10mm'BOOL_OP;OR;COMPOSITE_TEST;1;TEST @Value(subduct_size) = 0'N/A'FME_NUM_CONDITIONS11___
    -> FeatureMerger_6 [REQUESTOR]
Note: Feeder Cable
Junction_22
    -> SpatialRelator [Supplier]
SpatialRelator [off]
    AGGREGATE_HANDLING = Yes
    CALC_CARD = Yes
    CURVE_BOUNDARY_RULE_PARAM = Default Rule
    LIST_NAME = _relationships
    PREDICATES = INTERSECTS TOUCHES
    SUCCESS_ATTR = _related_suppliers
    -> Tester
Tester [off]
    BOOL_OP = OR
    TEST_CLAUSE = TEST @Value(_related_suppliers) != 0
    TEST_MODE = TEST
DuplicateFilter_4
    INPUT_ORDERED_CHOICE_LOOKUP = NO
    KEYATTR = chamber_network label pia_name
    INPUT_ORDERED_CHOICE = No
    UNIQUE -> CenterPointExtractor
CenterPointExtractor
    CENTX = _inside_x
    CENTY = _inside_y
    CENTZ = _inside_z
    EXTRACTIONMODE = CENTEROFGRAV
    -> FeatureMerger [REQUESTOR]
Note: Downstream HP
Junction_13
    -> FeatureMerger_6 [SUPPLIER]
FeatureMerger_6
    ATTR_ACCUM_MODE = Merge Supplier
    ATTR_CONFLICT_RES_LOOKUP = SUPPLIER_IF_CONFLICT
    IGNORE_NULLS = No
    JOIN_KEYS = @Value(name) @Value(name) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> CenterPointExtractor_2
    UNMERGED_REQUESTOR -> CenterPointExtractor_2
pia_chambers (reader POSTGIS_3)
    attributes: pia_name varchar(50), ent_id varchar(200), chamber_network varchar(7), label varchar(150), owner varchar(20), status varchar(20), itm_x varchar(200), itm_y varchar(200), chmbexist varchar(20), location varchar(20), accessible varchar(20), condition varchar(20), popspace varchar(20), pocspace varchar(20), thirdparty varchar(20), surface varchar(20), ch_type varchar(20), ch_condition varchar(20), remedial_civils varchar(20), ent_status varchar(20), cei_reference varchar(50), sdsi_reference varchar(50), subduct_size int4, olt_name varchar(10), map_url varchar(250)
    -> ChangeDetector_2 [ORIGINAL]
ChangeDetector
    BLANK_AND_MISSING_DIFFER = No
    CHECK_TYPES_AND_ENCODINGS = No
    MATCHATTRS = cei_reference ent_status level_ name sdsi_reference subduct_size total_duct_length downstream_hp olt_name map_url
    MATCH_STRATEGY_LOOKUP = MATCH
    PREEMPTIVE_ATTRS = pia_ent_id
    UNCHANGED_OUTPUT_LOOKUP = ORIGINAL
    UPSERT_MODE = No
    MATCH_STRATEGY = Match Selected Attributes
    UNCHANGED_OUTPUT = Output Original
    UPDATED -> FeatureWriter_3 [Output]
    INSERTED -> FeatureWriter_3 [Output]
    DELETED -> FeatureWriter_3 [Output]
FeatureWriter_3
    DATASET = VMK Public DB (postgres User)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = vmk_asbuilt
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written
ChangeDetector_2
    BLANK_AND_MISSING_DIFFER = No
    CHECK_TYPES_AND_ENCODINGS = No
    MATCHATTRS = accessible cei_reference ch_condition ch_type chamber_network chmbexist condition ent_status itm_x itm_y label location owner pia_ent_id pia_name pocspace popspace remedial_civils sdsi_reference status subduct_size surface thirdparty olt_name
    MATCH_STRATEGY_LOOKUP = MATCH
    PREEMPTIVE_ATTRS = ent_id
    UNCHANGED_OUTPUT_LOOKUP = ORIGINAL
    UPSERT_MODE = No
    MATCH_STRATEGY = Match Selected Attributes
    UNCHANGED_OUTPUT = Output Original
    UPDATED -> FeatureWriter_7 [Output]
    INSERTED -> FeatureWriter_7 [Output]
    DELETED -> FeatureWriter_7 [Output]
FeatureWriter_7
    DATASET = VMK Public DB (postgres User)
    DATASET_ATTR = _dataset
    FEATURE_TYPE_LIST_ATTR = _feature_types
    FORMAT = POSTGIS
    POSTGIS_BULK_COPY = YES
    POSTGIS_COORDINATE_SYSTEM_GRANULARITY = FEATURE_TYPE
    POSTGIS_GENERIC_GEOMETRY = yes
    POSTGIS_LOWERCASE_ATTRIBUTE_NAMES = Yes
    POSTGIS_NAMED_CONNECTION = vmk_asbuilt
    POSTGIS_SPATIAL_COLUMN_NAME = geom
    POSTGIS_SPATIAL_COLUMN_TYPE = geometry
    POSTGIS_SPLIT_MULTIGEOMETRIES = No
    POSTGIS_START_TRANSACTION = 0
    POSTGIS_STRICT_TEMPORAL_TYPE_HANDLING = Yes
    POSTGIS_TRANSACTION_INTERVAL = 1000
    TOTAL_FEATURES_WRITTEN_ATTR = _total_features_written

Bookmark: PIA Boundary
AttributeKeeper_4
    CREATE_BULK_MODE_FEATURES = NO
    KEEP_ATTRS = name,level_,cei_reference,ent_id,sdsi_reference,subduct_size,total_duct_length,ent_status
    -> AttributeRenamer_3
AttributeRenamer_3
    ATTR_TABLE = RENAME_SET_DEFAULT ent_id > pia_ent_id
    KEEP_RENAMED_ONLY = no
    MISSING_INPUT_ATTRS = REMOVE
    -> PIA_Boundary
PIA_Boundary: Tester
    BOOL_OP = COMPOSITE
    COMPOSITE_TEST = 1 AND 2 AND 3
    TEST_CLAUSE:
      TEST @Value(level_) = 15
      TEST @Value(ent_status) != 1
      CASE_INSENSITIVE_TEST @Value(name) BEGINS_WITH @Substring($(OLTName),3,3)
    TEST_MODE = PER_TEST
    PASSED -> Chambers_PIA [CLIPPER]
    PASSED -> AttributeCreator_6

Bookmark: Create the nodes with Network ID from Starting Point
Tester_4
    BOOL_OP = COMPOSITE
    COMPOSITE_TEST = 1 AND 2
    TEST_CLAUSE:
      CASE_INSENSITIVE_TEST @Value(enc_type) = 5
      CASE_INSENSITIVE_TEST @Value(label) CONTAINS @Right($(OLTName),3)
    TEST_MODE = CASE_INSENSITIVE_TEST
    PASSED -> Junction_17
    PASSED -> NetworkCostCalculator_2 [SOURCE]
    FAILED -> Junction_7
AttributeKeeper_6
    CREATE_BULK_MODE_FEATURES = NO
    KEEP_ATTRS = label,ent_status
    -> ent_status
ent_status: Tester
    BOOL_OP = OR
    TEST_CLAUSE = TEST @Value(ent_status) != 1
    TEST_MODE = TEST
    PASSED -> Junction_22
    PASSED -> Snapper
Snapper
    EXTEND_LINES = NEVER
    SAVE_SHORT_LINES = No
    SNAPTYPE = END_NODE
    TOLERANCE = 1
    SNAPPED -> TopologyBuilder_4
    SNAPPED -> Junction_6
    UNTOUCHED -> TopologyBuilder_4
    UNTOUCHED -> Junction_6
TopologyBuilder_4
    ALLOW_CYCLES = No
    CLEANING_TOLERANCE_LOOKUP = AUTO
    DEAGGREGATE_INPUT = Yes
    GENERATION_MODE = INTERSECT
    MAX = 0
    OVERLAPPING_MODE = No
    START_EDGES = No
    BOUNDING_EDGES = All
    CLEANING_TOLERANCE = Automatic
    LINE -> CRCCalculator_2
CRCCalculator_2
    ALG_TYPE = CRC_32
    CRC_ATTR = _crc
    CRC_TYPE = GEOM_ENCODED
    ALG_CHOICES = CRC-32
    -> DuplicateFilter
DuplicateFilter
    INPUT_ORDERED_CHOICE_LOOKUP = NO
    KEYATTR = _crc
    INPUT_ORDERED_CHOICE = No
    UNIQUE -> NetworkCostCalculator_2 [LINE]
    UNIQUE -> Junction_18
NetworkCostCalculator_2
    OUTPUT_CHOICE = MEASURE_VALUES
    SNAP_POINTS = Yes
    SNAP_TOLERANCE = 1.5
    WEIGHT_ATTR_CHOICE = By Length
    CONNECTED -> Chopper
    DISCONNECTED -> ListBuilder
Chopper
    DEAGGREGATE_INPUT = Deaggregate
    MAX_VERTICES = 1
    MODE_LOOKUP = VERTEX
    REMNANT_ATTR = _remnant
    MODE = By Vertex
    CHOPPED -> MeasureExtractor
MeasureExtractor
    GET_MODE = POINT
    MEASURE_ATTR = _point_measure
    GEOM_TYPE = Point
    -> Matcher
Matcher
    BLANK_AND_MISSING_DIFFER = No
    BLANK_AND_MISSING_NAMES_TRAITS_DIFFER = No
    CHECK_COORDINATE_SYSTEMS = No
    CHECK_TYPES_AND_ENCODINGS = No
    CNT_ATTR = _match_id
    LENIENT_MATCH = No
    MATCH = FULL
    MATCHATTRS = _point_measure
    MATCH_STRATEGY_LOOKUP = MATCH
    MATCH_STRATEGY = Match Selected Attributes
    SINGLE_MATCHED -> Sorter
    NOT_MATCHED -> Sorter
Sorter
    SORT_PARM = _point_measure NUMERIC ASCENDING
    SORTED -> Counter
Counter
    CNT_ATTR = _count
    DOMAIN = counter
    SCOPE = Global
    START = 1
    -> AttributeKeeper_8
AttributeKeeper_8
    CREATE_BULK_MODE_FEATURES = NO
    KEEP_ATTRS = _count
    -> Junction_16
    -> NeighborFinder_3 [CANDIDATE]
ListBuilder
    LIST_ATTRS_TO_INCLUDE = label
    LIST_NAME = _list
    -> ListConcatenator
ListConcatenator
    DROP_EMPTY_PARTS = No
    LIST_ATTR = _list{}.label
    SEP = ,
    VAL_ATTR = _concatenated
    -> Emailer
Note: Emailer for disconnected cables
Emailer
    AUTHENTICATION = YES
    BODY:
      Disconnected_Network

      @Value(_concatenated)
    ENCRYPTION = TLS
    FROM = fmeserver@entegro.ie
    HOST = smtp.office365.com
    PASSWORD =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
    PORT = 587
    SERVICE = Generic SMTP
    SMTP_CONNECTION = HOST;smtp.office365.com;PORT;587;ENCRYPTION;TLS;TIMEOUT_Generic_SMTP;60;AUTHENTICATION;YES;USERNAME;fmeserver@entegro.ie;PASSWORD;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;TIMEOUT;60
    SUBJECT = $(OLTName)_Disconnected Network
    TIMEOUT = 60
    TIMEOUT_Generic_SMTP = 60
    TO = $(email_address)
    USERNAME = fmeserver@entegro.ie

Bookmark: Extract the Home Count From Splice Closure to the Feeder Cable
Note: Splice Closure
Junction_7
    -> AttributeKeeper_3
AttributeKeeper_3
    CREATE_BULK_MODE_FEATURES = NO
    KEEP_ATTRS = home_count,label
    -> Junction_9
Note: Splice Clorure
Junction_9
    -> NeighborFinder_4 [CANDIDATE]
Note: Feeder Cable
Junction_6
    -> AttributeCreator
AttributeCreator
    ATTR_TABLE = SET_TO home_count
    -> Junction_10
    -> CoordinateExtractor_4
Note: Feeder Cable_Line
Junction_10
    -> FeatureMerger_3 [REQUESTOR]
Note: Extract end point of line
CoordinateExtractor_4
    IND = -1
    RECURSIVE = No
    X_ATTR = _x
    Y_ATTR = _y
    Z_ATTR = _z
    MODE = Specify Coordinate
    -> VertexCreator_4
VertexCreator_4
    MEASURE_TYPE_LOOKUP = CONTINUOUS
    MODE = REPLACE
    REMOVE_ATTRIBUTES = No
    XVAL = @Value(_x)
    YVAL = @Value(_y)
    MEASURE_TYPE = Continuous
    MODE_NAME = Replace with Point
    -> AttributeRenamer_2
AttributeRenamer_2
    ATTR_TABLE = RENAME_SET_DEFAULT label > cable_label
    KEEP_RENAMED_ONLY = no
    MISSING_INPUT_ATTRS = REMOVE
    -> Junction_8
Note: End_Point Fedder cable
Junction_8
    -> NeighborFinder_4 [BASE]
NeighborFinder_4
    ATTR_ACCUM_MODE = Merge Candidate
    ATTR_CONFLICT_RES = Use Candidate
    CANDIDATES_FIRST = No
    INSERT_VERTEX = No
    K = 1
    MEASURES_FROM_CANDIDATE = Yes
    MEASURE_TYPE = Continuous
    MODE = Bases and Candidates
    TREAT_POLYGON_AS = Lines
    MATCHED -> AttributeKeeper_10
AttributeKeeper_10
    CREATE_BULK_MODE_FEATURES = NO
    KEEP_ATTRS = cable_label,ent_status,home_count,label
    -> FeatureMerger_3 [SUPPLIER]
FeatureMerger_3
    ATTR_ACCUM_MODE = Merge Supplier
    ATTR_CONFLICT_RES_LOOKUP = SUPPLIER_IF_CONFLICT
    IGNORE_NULLS = No
    JOIN_KEYS = @Value(label) @Value(cable_label) AUTO
    MERGE_TYPE_VAL = ATTRIBUTES
    PROCESS_DUPS = NO
    REJECT_NULL_MISSING_KEYS = No
    SUPPLIERS_FIRST = No
    ATTR_CONFLICT_RES = Use Supplier
    MERGE_TYPE = Attributes Only
    MERGED -> ShortestPathFinder [NETWORK]
    MERGED -> Junction_11

Bookmark: Identify Chambers Ingress and Egress
NeighborFinder_3
    ATTR_ACCUM_MODE = Merge Candidate
    ATTR_CONFLICT_RES = Use Base
    CANDIDATES_FIRST = No
    INSERT_VERTEX = No
    K = 1
    MAX = .1
    MEASURES_FROM_CANDIDATE = Yes
    MEASURE_TYPE = Continuous
    MODE = Bases and Candidates
    TREAT_POLYGON_AS = Lines
    MATCHED -> AttributeKeeper_9
    UNMATCHED_BASE -> Junction_24
NeighborFinder
    ATTR_ACCUM_MODE = Merge Candidate
    ATTR_CONFLICT_RES = Use Base
    CANDIDATES_FIRST = No
    INSERT_VERTEX = No
    K = 1
    MAX = .1
    MEASURES_FROM_CANDIDATE = Yes
    MEASURE_TYPE = Continuous
    MODE = Bases and Candidates
    TREAT_POLYGON_AS = Lines
    MATCHED -> AttributeKeeper_9
AttributeKeeper_9
    CREATE_BULK_MODE_FEATURES = NO
    KEEP_ATTRS = name,_count,accessible,cei_reference,ch_condition,ch_type,chmbexist,condition,ent_status,itm_x,itm_y,label,location,owner,pocspace,popspace,remedial_civils,sdsi_reference,status,subduct_size,surface,thirdparty,pia_ent_id,ent_id
    -> Sorter_2
Sorter_2
    SORT_PARM = name NATURAL ASCENDING
    SORTED -> StatisticsCalculator
    SORTED -> Ingress [REQUESTOR]
    SORTED -> Egress [REQUESTOR]
StatisticsCalculator
    ATTR_ACCUM_MODE = None
    CALCULATION_MODE = NUMERIC
    FEAT_STATS = _count,NUMERIC_MODE,MIN,MAX,,,,,,,,,,,
    GROUP_BY = name
    SUMMARY -> Ingress [SUPPLIER]
    SUMMARY -> Egress [SUPPLIER]
Ingress: FeatureMerger
    ATTR_ACCUM_MODE = Merge Supplier
    ATTR_CONFLICT_RES_LOOKUP = REQUESTOR_IF_CONFLICT
    GROUP_BY = name
    IGNORE_NULLS = No
    JOIN_KEYS = @Value(_count) @Value(_count.min) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_4
AttributeCreator_4
    ATTR_TABLE = SET_TO chamber_network (varchar(7)) = Ingress
    -> Junction_14
    -> AttributeManager
Egress: FeatureMerger
    ATTR_ACCUM_MODE = Merge Supplier
    ATTR_CONFLICT_RES_LOOKUP = REQUESTOR_IF_CONFLICT
    GROUP_BY = name
    IGNORE_NULLS = No
    JOIN_KEYS = @Value(_count) @Value(_count.max) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> AttributeCreator_3
AttributeCreator_3
    ATTR_TABLE = SET_TO chamber_network (varchar(7)) = Egress
    -> AttributeManager
AttributeManager
    ATTR_TABLE:
      RENAME_SET_VALUE name > pia_name (varchar(50))
      SET_TO owner (int32) = FME_CONDITIONAL:DEFAULT_VALUE'_FME_NO_OP_'BOOL_OP;OR;COMPOSITE_TEST;1;TEST @Value(owner) = 1'Virgin Media'BOOL_OP;OR;COMPOSITE_TEST;1;TEST @Value(owner) = 2'EIR shared'BOOL_OP;OR;COMPOSITE_TEST;1;TEST @Value(owner) = 3'other - add comment'BOOL_OP;OR;COMPOSITE_TEST;1;TEST @Value(owner) = 4'EIR PIA'BOOL_OP;OR;COMPOSITE_TEST;1;TEST @Value(owner) = 4'ENET'BOOL_OP;OR;COMPOSITE_TEST;1;TEST @Value(owner) = 5'BT'BOOL_OP;OR;COMPOSITE_TEST;1;TEST @Value(owner) = 6'ESB'FME_NUM_CONDITIONS8___
      SET_TO status (int32) = FME_CONDITIONAL:DEFAULT_VALUE'_FME_NO_OP_'BOOL_OP;OR;COMPOSITE_TEST;1;TEST @Value(status) = 1'Existing'BOOL_OP;OR;COMPOSITE_TEST;1;TEST @Value(status) = 2'Proposed'BOOL_OP;OR;COMPOSITE_TEST;1;TEST @Value(status) = 3'Removed'BOOL_OP;OR;COMPOSITE_TEST;1;TEST @Value(status) = 4'Built'BOOL_OP;OR;COMPOSITE_TEST;1;TEST @Value(status) = 5'Existing(Built)'FME_NUM_CONDITIONS6___
      SET_TO chmbexist (int32) = FME_CONDITIONAL:DEFAULT_VALUE'_FME_NO_OP_'BOOL_OP;OR;COMPOSITE_TEST;1;TEST @Value(chmbexist) = 1'Existing chamber'BOOL_OP;OR;COMPOSITE_TEST;1;TEST @Value(chmbexist) = 2'Proposed new chamber'BOOL_OP;OR;COMPOSITE_TEST;1;TEST @Value(chmbexist) = 3'Chamber does not exist'BOOL_OP;OR;COMPOSITE_TEST;1;TEST @Value(chmbexist) = 4'Built'FME_NUM_CONDITIONS5___
      SET_TO location (int32) = FME_CONDITIONAL:DEFAULT_VALUE'_FME_NO_OP_'BOOL_OP;OR;COMPOSITE_TEST;1;TEST @Value(location) = 1'Public'BOOL_OP;OR;COMPOSITE_TEST;1;TEST @Value(location) = 2'Private - no wayleave required'BOOL_OP;OR;COMPOSITE_TEST;1;TEST @Value(location) = 3'Private - wayleave required'BOOL_OP;OR;COMPOSITE_TEST;1;TEST @Value(location) = 4'Other - add comment'FME_NUM_CONDITIONS5___
      SET_TO accessible (int32) = FME_CONDITIONAL:DEFAULT_VALUE'_FME_NO_OP_'BOOL_OP;OR;COMPOSITE_TEST;1;TEST @Value(accessible) = 1'Yes'BOOL_OP;OR;COMPOSITE_TEST;1;TEST @Value(accessible) = 2'Buried - minor (no civils required)'BOOL_OP;OR;COMPOSITE_TEST;1;TEST @Value(accessible) = 3'Buried - major (civils required)'BOOL_OP;OR;COMPOSITE_TEST;1;TEST @Value(accessible) = 4'Other - add comment'FME_NUM_CONDITIONS5___
      SET_TO condition (int32) = FME_CONDITIONAL:DEFAULT_VALUE'_FME_NO_OP_'BOOL_OP;OR;COMPOSITE_TEST;1;TEST @Value(condition) = 1'Good'BOOL_OP;OR;COMPOSITE_TEST;1;TEST @Value(condition) = 2'Silted'BOOL_OP;OR;COMPOSITE_TEST;1;TEST @Value(condition) = 3'Flooded'BOOL_OP;OR;COMPOSITE_TEST;1;TEST @Value(condition) = 4'Heavy debris'BOOL_OP;OR;COMPOSITE_TEST;1;TEST @Value(condition) = 5'Repeat gas test failure'BOOL_OP;OR;COMPOSITE_TEST;1;TEST @Value(condition) = 6'Other - add comment'FME_NUM_CONDITIONS7___
      SET_TO popspace (int32) = FME_CONDITIONAL:DEFAULT_VALUE'_FME_NO_OP_'BOOL_OP;OR;COMPOSITE_TEST;1;TEST @Value(popspace) = 1'Yes'BOOL_OP;OR;COMPOSITE_TEST;1;TEST @Value(popspace) = 2'No'BOOL_OP;OR;COMPOSITE_TEST;1;TEST @Value(popspace) = 3'Unable to determine'FME_NUM_CONDITIONS4___
      SET_TO pocspace (int32) = FME_CONDITIONAL:DEFAULT_VALUE'_FME_NO_OP_'BOOL_OP;OR;COMPOSITE_TEST;1;TEST @Value(pocspace) = 1'Yes'BOOL_OP;OR;COMPOSITE_TEST;1;TEST @Value(pocspace) = 2'No'BOOL_OP;OR;COMPOSITE_TEST;1;TEST @Value(pocspace) = 3'Unable to determine'FME_NUM_CONDITIONS4___
      SET_TO thirdparty (int32) = FME_CONDITIONAL:DEFAULT_VALUE'_FME_NO_OP_'BOOL_OP;OR;COMPOSITE_TEST;1;TEST @Value(thirdparty) = 1'Yes'BOOL_OP;OR;COMPOSITE_TEST;1;TEST @Value(thirdparty) = 2'No'BOOL_OP;OR;COMPOSITE_TEST;1;TEST @Value(thirdparty) = 3'Unable to determine'FME_NUM_CONDITIONS4___
      SET_TO surface (int32) = FME_CONDITIONAL:DEFAULT_VALUE'_FME_NO_OP_'BOOL_OP;OR;COMPOSITE_TEST;1;TEST @Value(surface) = 1'Grass/verge'BOOL_OP;OR;COMPOSITE_TEST;1;TEST @Value(surface) = 2'Footway'BOOL_OP;OR;COMPOSITE_TEST;1;TEST @Value(surface) = 3'Carriageway'BOOL_OP;OR;COMPOSITE_TEST;1;TEST @Value(surface) = 4'Cobble'FME_NUM_CONDITIONS5___
      SET_TO ch_type (int32) = FME_CONDITIONAL:DEFAULT_VALUE'_FME_NO_OP_'BOOL_OP;OR;COMPOSITE_TEST;1;TEST @Value(ch_type) = 1'FW1'BOOL_OP;OR;COMPOSITE_TEST;1;TEST @Value(ch_type) = 2'FW2'BOOL_OP;OR;COMPOSITE_TEST;1;TEST @Value(ch_type) = 3'FW3'BOOL_OP;OR;COMPOSITE_TEST;1;TEST @Value(ch_type) = 4'FW4/JB4'BOOL_OP;OR;COMPOSITE_TEST;1;TEST @Value(ch_type) = 5'FW5/JB5'BOOL_OP;OR;COMPOSITE_TEST;1;TEST @Value(ch_type) = 6'FW6/JB6'BOOL_OP;OR;COMPOSITE_TEST;1;TEST @Value(ch_type) = 7'Round Chamber'BOOL_OP;OR;COMPOSITE_TEST;1;TEST @Value(ch_type) = 8'Non Standard Chamber'BOOL_OP;OR;COMPOSITE_TEST;1;TEST @Value(ch_type) = 10'FW10 (JB4C)'BOOL_OP;OR;COMPOSITE_TEST;1;TEST @Value(ch_type) = 11'CW1'BOOL_OP;OR;COMPOSITE_TEST;1;TEST @Value(ch_type) = 12'CW2'BOOL_OP;OR;COMPOSITE_TEST;1;TEST @Value(ch_type) = 14'CW4'BOOL_OP;OR;COMPOSITE_TEST;1;TEST @Value(ch_type) = 15'JB4A (2 lids)'BOOL_OP;OR;COMPOSITE_TEST;1;TEST @Value(ch_type) = 16'JB4B (3 lids)'BOOL_OP;OR;COMPOSITE_TEST;1;TEST @Value(ch_type) = 17'Elkington'FME_NUM_CONDITIONS16___
      SET_TO ch_condition (int32) = FME_CONDITIONAL:DEFAULT_VALUE'_FME_NO_OP_'BOOL_OP;OR;COMPOSITE_TEST;1;TEST @Value(ch_condition) = 1'Suitable for build'BOOL_OP;OR;COMPOSITE_TEST;1;TEST @Value(ch_condition) = 2'Chamber collapsed'BOOL_OP;OR;COMPOSITE_TEST;1;TEST @Value(ch_condition) = 3'Reset frame and cover'BOOL_OP;OR;COMPOSITE_TEST;1;TEST @Value(ch_condition) = 4'New lid required'BOOL_OP;OR;COMPOSITE_TEST;1;TEST @Value(ch_condition) = 5'Heavily flooded (duct mouth covered)'BOOL_OP;OR;COMPOSITE_TEST;1;TEST @Value(ch_condition) = 6'Heavily silted (duct mouth covered)'BOOL_OP;OR;COMPOSITE_TEST;1;TEST @Value(ch_condition) = 7'Other - add comment'FME_NUM_CONDITIONS8___
      SET_TO remedial_civils (int32) = FME_CONDITIONAL:DEFAULT_VALUE'_FME_NO_OP_'BOOL_OP;OR;COMPOSITE_TEST;1;TEST @Value(remedial_civils) = 1'N/A'BOOL_OP;OR;COMPOSITE_TEST;1;TEST @Value(remedial_civils) = 2'Demolish and replace (with similar)'BOOL_OP;OR;COMPOSITE_TEST;1;TEST @Value(remedial_civils) = 3'Demolish and replace (with Different)'BOOL_OP;OR;COMPOSITE_TEST;1;TEST @Value(remedial_civils) = 4'Replace cover and frame'BOOL_OP;OR;COMPOSITE_TEST;1;TEST @Value(remedial_civils) = 5'Reset cover and frame'BOOL_OP;OR;COMPOSITE_TEST;1;TEST @Value(remedial_civils) = 6'Desilt'BOOL_OP;OR;COMPOSITE_TEST;1;TEST @Value(remedial_civils) = 7'Pump out'FME_NUM_CONDITIONS8___
      REMOVE _count (int64)
      REMOVE _count.min (int64)
      REMOVE _count.max (int64)
      SET_TO olt_name (varchar(200)) = $(OLTName)
    USER_EXPOSED_ATTRIBUTES = olt_name
    -> DuplicateFilter_4

Bookmark: Extract_Start_Point
Tester_5
    BOOL_OP = OR
    TEST_CLAUSE = TEST @Value(_count) = 1
    TEST_MODE = TEST
    PASSED -> CoordinateExtractor_3
CoordinateExtractor_3
    IND = 0
    RECURSIVE = No
    X_ATTR = _x
    Y_ATTR = _y
    Z_ATTR = _z
    MODE = Specify Coordinate
    -> AttributeRenamer_4
AttributeRenamer_4
    ATTR_TABLE:
      RENAME_SET_DEFAULT _x > x_s
      RENAME_SET_DEFAULT _y > y_s
    KEEP_RENAMED_ONLY = no
    MISSING_INPUT_ATTRS = REMOVE
    -> FeatureMerger_4 [SUPPLIER]
    -> NetworkFlowOrientor [DESTINATION]
    -> FeatureMerger_7 [SUPPLIER]
FeatureMerger_4
    ATTR_ACCUM_MODE = Merge Supplier
    ATTR_CONFLICT_RES_LOOKUP = REQUESTOR_IF_CONFLICT
    IGNORE_NULLS = No
    JOIN_KEYS = 1 1 AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> VertexCreator_3

Bookmark: From to line creation
Note: Start point of line
VertexCreator_2
    MODE = REPLACE
    XVAL = @Value(_x)
    YVAL = @Value(_y)
    MODE_NAME = Replace with Point
    -> FeatureMerger_4 [REQUESTOR]
Note: End point of network
VertexCreator_3
    MODE = ADD
    XVAL = @Value(x_s)
    YVAL = @Value(y_s)
    MODE_NAME = Add Point
    -> ShortestPathFinder [FROM-TO]

Bookmark: Add Map URL
agol_id (reader POSTGRES_2)
    attributes: map_name varchar(31), olt_name varchar(7), map_id varchar(32), map_type varchar(20)
    -> Tester_7
Tester_7
    BOOL_OP = OR
    TEST_CLAUSE = TEST @Value(map_type) = Feeder Map
    TEST_MODE = TEST
    PASSED -> StringReplacer_3
StringReplacer_3
    CASE = NO
    FIND_TEXT = -
    NO_MATCH = _FME_NO_OP_
    REGEXP = NO
    SRC_ATTRS = olt_name
    -> Junction_15
    -> FeatureMerger [SUPPLIER]
FeatureMerger
    ATTR_ACCUM_MODE = Merge Supplier
    ATTR_CONFLICT_RES_LOOKUP = REQUESTOR_IF_CONFLICT
    IGNORE_NULLS = No
    JOIN_KEYS = @Value(olt_name) @Value(olt_name) AUTO
    MERGE_TYPE_VAL = ATTRIBUTES
    PRESERVE_FEATURE_ORDER_LOOKUP = PER_OUTPUT_PORT
    PROCESS_DUPS = NO
    REJECT_NULL_MISSING_KEYS = No
    SUPPLIERS_FIRST = No
    ATTR_CONFLICT_RES = Use Requestor
    MERGE_TYPE = Attributes Only
    MERGED -> AttributeCreator_43
AttributeCreator_43
    ATTR_TABLE = SET_TO map_url (varchar(200)) = https://ipone.maps.arcgis.com/apps/mapviewer/index.html?webmap=@Value(map_id)&center=@Value(_inside_x),@Value(_inside_y),29903&level=30
    -> ChangeDetector_2 [REVISED]
